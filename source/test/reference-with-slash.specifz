# reference with slash
- Rights: Creative Commons 4.0 CC BY-SA, https://creativecommons.org/licenses/by-sa/4.0/

## Project Information (SpecIF:Heading)
- dcterms:description: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
  This specification method integrates and represents:
  - processes, system composition and requirements (dynamic, static and detail views)
  - mechanic, electric and software components with their interfaces.
  It is important to understand, that all plans (diagrams) are views of a common system engineering model, sometimes called 'system repository'. Thus, consistency is always maintained.
  The model elements are connected with statements, most of which are defined by positioning graph elements. For example, if a system component is drawn within another, a relationship 'contains' is created in the logic representation of the engineering model. Other statements, such as a system component 'complies-with' a requirement are created manually.
  Also, the documents are generated from the system engineering model. The ordering is in most projects (it can be rearranged, however, if appropriate):
  - All plans
  - A glossary with descriptions of all model elements appearing on one or more plans
  - A hierarchically ordered list of requirements
  - A list of open issues.
  Please note that plans list related model elements and model elements list related requirements .. and vice versa. Active hyper-links are used, so that it is easy to jump between related model elements.
  Stakeholders:
  | Name | Organisation | Telephone | Email |
  | --- | --- | --- | --- |
  | Vorname Nachname | Hersteller AG |  |  |
  Legend:
  To distinguish their type, element names are preceded by one of the following symbols:
  | ▣ | Plan | A 'Diagram' is a graphical model view with a specific communication purpose, e.g. a business process or system composition. |
  | --- | --- | --- |
  | ■ | Actor (Role, Function) | An 'Actor' is a fundamental model element type representing an active entity, be it an activity, a process step, a function, a system component or a role. |
  | ● | State (Information) | A 'State' is a fundamental model element type representing a passive entity, be it a value, a condition, an information storage or even a physical shape. |
  | ♦ | Event | An 'Event' is a fundamental model element type representing a time reference, a change in condition/value or more generally a synchronisation primitive. |
  | ✶ | Feature | A 'Feature' is an intentional distinguishing characteristic of a system, often a unique selling proposition. |
  | ↯ | Requirement | A 'Requirement' is a singular documented physical and functional need that a particular design, product or process must be able to perform. |
- SpecIF:Type: Folder
